module hello2-impl {
    yang-version 1;
    namespace "urn:opendaylight:params:xml:ns:yang:hello2:impl";
    prefix "hello2-impl";

    import config { prefix config; revision-date 2013-04-05; }
    import opendaylight-md-sal-binding { prefix md-sal-binding; revision-date 2013-10-28;}

    description
        "Service definition for hello2 project";

    revision "2014-12-10" {
        description
            "Initial revision";
    }

    identity hello2 {
        base config:module-type;
        config:java-name-prefix Hello2;
    }

    augment "/config:modules/config:module/config:configuration" {
        case hello2 {
            when "/config:modules/config:module/config:type = 'hello2'";
            container broker {
                uses config:service-ref {
                    refine type {
                        mandatory true;
                        config:required-identity md-sal-binding:binding-broker-osgi-registry;
                    }
                }
            }
        }
    }
}
